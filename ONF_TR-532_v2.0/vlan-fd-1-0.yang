module vlan-fd-1-0 {
  yang-version 1.1;
  namespace "urn:onf:yang:vlan-fd-1-0";
  prefix vlan-fd;

  import ietf-yang-types {
    prefix yang;
  }
  import core-model-1-4 {
    prefix core-model;
  }
  import vlan-interface-1-0 {
    prefix vlan-interface;
  }

  organization
    "openBackhaul.com proposal to Open Networking Foundation (ONF)";
  contact
    "WG Web : https://github.com/openBackhaul/Overview
     WG List: VlanFd@openBackhaul.com
     Editor : Thorsten Heinze
     Email  : Thorsten.Heinze@openBackhaul.com";
  description
    "Technology specific Forwarding Domain for VLAN Components according to IEEE 802.1Q-2018.

     Copyright 2024 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2024-01-04 {
    description
      "Model for the Transport SDN Introduction at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }
  revision 2022-04-07 {
    description
      "Model for the Transport SDN Pilot at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }
  revision 2021-01-26 {
    description
      "Model for the Transport SDN Pilot at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }
  revision 2021-01-05 {
    description
      "Model for the Transport SDN Pilot at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }
  revision 2020-08-26 {
    description
      "Model for the Transport SDN Pilot at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }
  revision 2019-08-19 {
    description
      "Model for the Transport SDN Pilot at Telefonica Germany.
       Please view https://github.com/openBackhaul/vlanFd/issues for changes.";
    reference
      "https://github.com/openBackhaul/vlanFd/tree/tsi: Model definition
       https://github.com/openBackhaul/onfCoreIm/tree/tsi: ONF TR-512 Core IM incl. Profile and enhanced Equipment definition";
  }

  /*********************************************
   * grouping statements for complex data types
   *******************************************/ 

  identity SUB_LAYER_PROTOCOL_NAME_TYPE {
    description
      "none";
  }

  identity SUB_LAYER_PROTOCOL_NAME_TYPE_C_VLAN_COMPONENT {
    base SUB_LAYER_PROTOCOL_NAME_TYPE;
    description
      "Base identity for a C-VLAN component. Name in ieee802-dot1q-bridge.yang: c-vlan-component.";
  }

  identity SUB_LAYER_PROTOCOL_NAME_TYPE_S_VLAN_COMPONENT {
    base SUB_LAYER_PROTOCOL_NAME_TYPE;
    description
      "Base identity for a S-VLAN component. Name in ieee802-dot1q-bridge.yang: s-vlan-component.";
  }

  identity SUB_LAYER_PROTOCOL_NAME_TYPE_D_BRIDGE_COMPONENT {
    base SUB_LAYER_PROTOCOL_NAME_TYPE;
    description
      "Base identity for a VLAN unaware component. Name in ieee802-dot1q-bridge.yang: d-bridge-component.";
  }

  identity SUB_LAYER_PROTOCOL_NAME_TYPE_EDGE_RELAY_COMPONENT {
    base SUB_LAYER_PROTOCOL_NAME_TYPE;
    description
      "Base identity for an EVB station ER component. Name in ieee802-dot1q-bridge.yang: edge-relay-component. ";
  }

  identity SUB_LAYER_PROTOCOL_NAME_TYPE_NOT_YET_DEFINED {
    base SUB_LAYER_PROTOCOL_NAME_TYPE;
    description
      "none";
  }

  identity PROTOCOL_FRAME_FORMAT_TYPE {
    description
      "none";
  }

  identity PROTOCOL_FRAME_FORMAT_TYPE_ETHERNET {
    base PROTOCOL_FRAME_FORMAT_TYPE;
    description
      "Ethernet frame format. Name in ieee802-dot1q-bridge.yang: Ethernet.";
  }

  identity PROTOCOL_FRAME_FORMAT_TYPE_RFC1042 {
    base PROTOCOL_FRAME_FORMAT_TYPE;
    description
      "RFC 1042 frame format. Name in ieee802-dot1q-bridge.yang: rfc1042.";
  }

  identity PROTOCOL_FRAME_FORMAT_TYPE_SNAP8021H {
    base PROTOCOL_FRAME_FORMAT_TYPE;
    description
      "SNAP 802.1H frame format. Name in ieee802-dot1q-bridge.yang: snap8021H.";
  }

  identity PROTOCOL_FRAME_FORMAT_TYPE_SNAP_OTHER {
    base PROTOCOL_FRAME_FORMAT_TYPE;
    description
      "Other SNAP frame format. Name in ieee802-dot1q-bridge.yang: snapOther.";
  }

  identity PROTOCOL_FRAME_FORMAT_TYPE_LLC_OTHER {
    base PROTOCOL_FRAME_FORMAT_TYPE;
    description
      "Other LLC frame format. Name in ieee802-dot1q-bridge.yang: llcOther.";
  }

  identity PROTOCOL_FRAME_FORMAT_TYPE_NOT_YET_DEFINED {
    base PROTOCOL_FRAME_FORMAT_TYPE;
    description
      "none";
  }

  identity FD_STATUS_TYPE {
    description
      "none";
  }

  identity FD_STATUS_TYPE_UP {
    base FD_STATUS_TYPE;
    description
      "Ready to pass packets.";
  }

  identity FD_STATUS_TYPE_DOWN {
    base FD_STATUS_TYPE;
    description
      "The interface does not pass any packets.";
  }

  identity FD_STATUS_TYPE_TESTING {
    base FD_STATUS_TYPE;
    description
      "In some test mode.  No operational packets can be passed.";
  }

  identity FD_STATUS_TYPE_UNKNOWN {
    base FD_STATUS_TYPE;
    description
      "Status cannot be determined for some reason.";
  }

  identity FD_STATUS_TYPE_DORMANT {
    base FD_STATUS_TYPE;
    description
      "Waiting for some external event.";
  }

  identity FD_STATUS_TYPE_NOT_PRESENT {
    base FD_STATUS_TYPE;
    description
      "Some component (typically hardware) is missing.";
  }

  identity FD_STATUS_TYPE_LOWER_LAYER_DOWN {
    base FD_STATUS_TYPE;
    description
      "Down due to state of lower-layer interface(s).";
  }

  identity FD_STATUS_TYPE_ADMIN_DOWN {
    base FD_STATUS_TYPE;
    description
      "Down due to configuration.";
  }

  identity FD_STATUS_TYPE_NOT_YET_DEFINED {
    base FD_STATUS_TYPE;
    description
      "none";
  }

  /****************************************
   * typedef statements
   **************************************/ 

  typedef sub-layer-protocol-name-type {
    type identityref {
      base SUB_LAYER_PROTOCOL_NAME_TYPE;
    }
    description
      "Represents the type of Component. Name in ieee802-dot1q-bridge.yang: type-of-component.";
  }

  typedef protocol-frame-format-type {
    type identityref {
      base PROTOCOL_FRAME_FORMAT_TYPE;
    }
    description
      "A value representing the frame format to be matched. Name in ieee802-dot1q-bridge.yang: protocol-frame-format-type.";
  }

  /****************************************
   * package super-types
   **************************************/ 

  typedef fd-status-type {
    type identityref {
      base FD_STATUS_TYPE;
    }
    description
      "Current Status of the Forwarding Domain";
  }

  /****************************************
   * grouping statements for object classes
   **************************************/ 

  grouping vlan-fd-spec {
    description
      "The set of components associated with a given Bridge. For example, - A TPMR is associated with a single VLAN unaware component. - A Customer VLAN Bridge is associated with a single VLAN aware component. - A Provider Bridge is associated with a single S-VLAN component and zero or more C-VLAN components. Name in ieee802-dot1q-bridge.yang: component.";
    container vlan-fd-pac {
      description
        "none";
      uses vlan-fd-pac;
    }
  }

  grouping vlan-fd-pac {
    description
      "none";
    container vlan-fd-capability {
      config false;
      description
        "none";
      uses vlan-fd-capability;
    }
    container vlan-fd-configuration {
      description
        "none";
      uses vlan-fd-configuration;
    }
    container vlan-fd-status {
      config false;
      description
        "none";
      uses vlan-fd-status;
    }
  }

  grouping vlan-fd-capability {
    description
      "none";
    leaf-list supported-sub-layer-protocol-name-list {
      type sub-layer-protocol-name-type;
      default "SUB_LAYER_PROTOCOL_NAME_TYPE_NOT_YET_DEFINED";
      config false;
      description
        "Lists the supported kinds of Components. ";
    }
    leaf component-id {
      type int32;
      default "-1";
      config false;
      description
        "Unique identifier for a particular Bridge component within the system. Name in ieee802-dot1q-bridge.yang: id.";
    }
    leaf extended-filtering-is-avail {
      type boolean;
      default "false";
      config false;
      description
        "true = Component can perform filtering on individual multicast addresses controlled by MMRP (Multiple MAC Registration Protocol). Name in ieee802-dot1q-bridge.yang: extended-filtering.";
    }
    leaf traffic-classes-is-avail {
      type boolean;
      default "false";
      config false;
      description
        "true = Component can map the Priority values into multiple traffic classes (there is more than one traffic class at the device). Name in ieee802-dot1q-bridge.yang: traffic-classes.";
    }
    leaf priority-to-traffic-class-mapping-is-avail {
      type boolean;
      default "false";
      config false;
      description
        "true = configuring the mapping of the Priority values into Traffic Classes (queues) is available as a configuration, which is common to all interfaces at the switch.";
    }
    leaf static-entries-on-individual-ports-is-avail {
      type boolean;
      default "false";
      config false;
      description
        "true = Static entries per port are available. Name in ieee802-dot1q-bridge.yang: static-entry-individual-port.";
    }
    leaf independent-vlan-learning-is-avail {
      type boolean;
      default "false";
      config false;
      description
        "true = Component supports Independent VLAN Learning (IVL). Name in ieee802-dot1q-bridge.yang: ivl-capable.";
    }
    leaf shared-vlan-learning-is-avail {
      type boolean;
      default "false";
      config false;
      description
        "true = Component supports Shared VLAN Learning (SVL). Name in ieee802-dot1q-bridge.yang: svl-capable.";
    }
    leaf hybrid-vlan-learning-is-avail {
      type boolean;
      default "false";
      config false;
      description
        "true = Component supports both Independent and Shared VLAN Learning simultaneously. Name in ieee802-dot1q-bridge.yang: hybrid-capable.";
    }
    leaf configurable-port-vlan-id-tagging-is-avail {
      type boolean;
      default "false";
      config false;
      description
        "true = Component supports setting the egress status (VLAN-tagged or Untagged) on each port. Name in ieee802-dot1q-bridge.yang: configurable-pvid-tagging.";
    }
    leaf multiple-local-bridges-is-avail {
      type boolean;
      default "false";
      config false;
      description
        "true = Can support multiple local Bridges, outside the scope of 802.1Q defined VLANs. Name in ieee802-dot1q-bridge.yang: local-vlan-capable.";
    }
    leaf supported-version {
      type int16;
      default "-1";
      config false;
      description
        "The version number supported. Name in ieee802-dot1q-bridge.yang: version.";
    }
    leaf maximum-number-of-vlan-ids {
      type int16;
      default "-1";
      config false;
      description
        "The maximum number of VLAN IDs supported. Name in ieee802-dot1q-bridge.yang: max-vids.";
    }
    leaf overriding-default-port-vlan-id-is-avail {
      type boolean;
      default "false";
      config false;
      description
        "true = Component supports overriding the default PVID on each port. Name in ieee802-dot1q-bridge.yang: override-default-pvid.";
    }
    leaf protocol-frame-format {
      type protocol-frame-format-type;
      default "PROTOCOL_FRAME_FORMAT_TYPE_NOT_YET_DEFINED";
      config false;
      description
        "The data-link encapsulation format or the detagged_frame_type in a Protocol Template. Name in ieee802-dot1q-bridge.yang: protocol-template.";
    }
    leaf maximum-number-of-msti {
      type int16;
      default "-1";
      config false;
      description
        "Maximum number of Multiple Spanning Tree Instances (MSTIs) supported within an MST region (i.e., the number of spanning tree instances that can be supported in addition to the CIST), for MST Bridges. For SST Bridges, this parameter may be either omitted or reported as 0.  Name in ieee802-dot1q-bridge.yang: max-msti.";
    }
    leaf port-and-protocol-based-vlan-is-avail {
      type boolean;
      default "false";
      config false;
      description
        "true = Restricting forwarding of frames of specific VLANs on specific protocols is available on this VLAN Bridge. Name in ieee802-dot1q-bridge.yang: protocol-based-vlan-classification.";
    }
  }

  grouping vlan-fd-configuration {
    description
      "none";
    leaf fd-name {
      type string;
      default "Forwarding Domain name not yet defined.";
      description
        "The name of the Component. Free text field to be filled by the operator. Name in ieee802-dot1q-bridge.yang: name.";
    }
    leaf sub-layer-protocol-name {
      type sub-layer-protocol-name-type;
      default "SUB_LAYER_PROTOCOL_NAME_TYPE_NOT_YET_DEFINED";
      description
        "The type of Component used to classify a particular Bridge component within a Bridge system comprising multiple components. Name in ieee802-dot1q-bridge.yang: type.\n";
    }
    leaf traffic-classes-is-on {
      type boolean;
      default "false";
      description
        "Only effective if (trafficClassesIsAvail==true). true = Traffic Classes are enabled on this Bridge Component. false = Bridge Component operates with a single priority level for all traffic. Name in ieee802-dot1q-bridge.yang: traffic-class-enabled.";
    }
    list protocol-group-list {
      key "db-index";
      description
        "Only effective if (portAndProtocolBasedVlanIsAvail==true). List of the protocol group database entries. Name in ieee802-dot1q-bridge.yang: protocol-group-database.";
      uses protocol-group-type;
    }
    list priority-to-traffic-class-mapping-list {
      key "priority-value";
      max-elements 8;
      description
        "Mapping of the Priority values into Traffic Classes (queues). This attribute is shortening the ieee802-dot1q-bridge.yang from a table to a list, because it allows only configuring the values for the number of traffic classes actually available at the device. Name in ieee802-dot1q-bridge.yang: traffic-class-map.
            ";
      uses priority-to-traffic-class-mapping-type;
    }
  }

  grouping vlan-fd-status {
    description
      "none";
    leaf number-of-ports-cur {
      type int16;
      default "-1";
      config false;
      description
        "Number of Bridge Ports associated with the Bridge Component. Values between 1 and 4095. Name in ieee802-dot1q-bridge.yang: ports.";
    }
    leaf number-of-static-vlan-registrations-cur {
      type int32;
      default "-1";
      config false;
      description
        "The number of Static VLAN Registration entries currently in the FDB. Name in ieee802-dot1q-bridge.yang: static-vlan-registration-entries.";
    }
    leaf number-of-dynamic-vlan-registrations-cur {
      type int32;
      default "-1";
      config false;
      description
        "The number of Dynamic VLAN Registration entries currently in the FDB. Name in ieee802-dot1q-bridge.yang: static-vlan-registration-entries.";
    }
    leaf fd-status {
      type fd-status-type;
      default "FD_STATUS_TYPE_NOT_YET_DEFINED";
      config false;
      description
        "Operational status of the forwarding domain.";
    }
  }

  grouping protocol-group-type {
    description
      "none";
    leaf db-index {
      type uint16;
      mandatory true;
      description
        "The protocol group database index. Name in ieee802-dot1q-bridge.yang: db-index.";
    }
    leaf protocol-group-id {
      type int32;
      default "-1";
      description
        "Designates a group of protocols in the Protocol Group Database. Name in ieee802-dot1q-bridge.yang: group-id.";
    }
    leaf protocol-frame-format {
      type protocol-frame-format-type;
      default "PROTOCOL_FRAME_FORMAT_TYPE_NOT_YET_DEFINED";
      description
        "The data-link encapsulation format or the detagged_frame_type in a Protocol Template. Name in ieee802-dot1q-bridge.yang: frame-format-type.";
    }
    leaf ethertype {
      type string;
      default "Ethertype not yet defined.";
      description
        "Only relevant if (protocolFrameFormat==ETHERNET) OR (protocolFrameFormat==RFC1042) OR (protocolFrameFormat==SNAP8021H). Format containing the 16-bit IEEE 802 EtherType field. The EtherType value represented in the canonical order defined by IEEE 802. The canonical representation uses uppercase characters. Pattern '[0-9a-fA-F]{2}-[0-9a-fA-F]{2}'. Name in ieee802-dot1q-bridge.yang: ethertype.";
    }
    leaf protocol-id {
      type string;
      default "Protocol ID not yet defined.";
      description
        "Only effective if (protocolFrameFormat==SNAP_OTHER). Format containing the 40-bit protocol identifier (PID). The canonical representation uses uppercase characters. Pattern '[0-9a-fA-F]{2}(-[0-9a-fA-F]{2}){4}'. Name in ieee802-dot1q-bridge.yang: protocol-id.";
    }
    leaf-list llc-address-list {
      type string;
      default "LLC Address not yet defined.";
      description
        "Only effective if (protocolFrameFormat==LLC_OTHER). A pair of ISO/IEC 8802-2 DSAP and SSAP address field values, for matching frame formats of LLC_Other. The canonical representation uses uppercase characters. Pattern '[0-9a-fA-F]{2}-[0-9a-fA-F]{2}'. Name in ieee802-dot1q-bridge.yang: llc-address.";
    }
  }

  grouping priority-to-traffic-class-mapping-type {
    description
      "If no corresponding PriorityToTrafficClassMappingType instance exists, the mapping of the respective Priority shall follow the standard, which is defined in Table 8-5 on page 198 of IEEE802.1Q-2018. This modeling is shortening the ieee802-dot1q-bridge.yang from a table to a list, because it allows only configuring the values for the number of traffic classes, which is actually available at the device. Name in ieee802-dot1q-bridge.yang: traffic-class-table-grouping.";
    leaf priority-value {
      type int8;
      mandatory true;
      description
        "Priority value, which is to be mapped into a Traffic Class (queue). Values from 0 to 7 (inclusive). Name in ieee802-dot1q-bridge.yang: priority.";
    }
    leaf traffic-class-value {
      type int8;
      default "-1";
      description
        "Index of the Traffic Class (queue), which gets associated with the Priority Value. Values from 0 to 7 (inclusive). Name in ieee802-dot1q-bridge.yang: traffic-class.";
    }
  }

  /****************************************
   * package interfaces
   **************************************/ 

  rpc create-vlan-fc {
    description
      "Creates a new VLAN of the same sub layer protocol of the referenced VLAN Bridge. A reference to the VLAN Bridge and the VLAN ID must be provided as input. The resulting VLAN will not yet connect to any interface. The following error-messages are to be send, if the operation would fail: #[onf:VLAN ID not available.]#, if the VLAN ID is either out of range of configurable values or occupied by some special service. #[onf:Referenced object is invalid.]#, if the referenced ForwardingDomain does not exist or does not belong to the VLAN layer. #[onf:Resources not available.]#, if e.g. the VLAN table would already be full.";
    input {
      leaf affected-vlan-fd {
        type leafref {
          path "/core-model:control-construct/core-model:forwarding-domain/core-model:uuid";
          require-instance false;
        }
        mandatory true;
        description
          "Reference of the VLAN Bridge, which shall implement the to be created VLAN.";
      }
      leaf new-vlan-id {
        type uint64;
        mandatory true;
        description
          "VLAN ID of the to be created VLAN.";
      }
    }
    output {
      leaf created-vlan-fc {
        type leafref {
          path "/core-model:control-construct/core-model:forwarding-domain/core-model:fc/core-model:uuid";
          require-instance false;
        }
        mandatory true;
        description
          "Reference of the VLAN (either newly created or already existing) with the VLAN ID, which had been provided as input.";
      }
    }
  }

  rpc delete-vlan-fc {
    description
      "Removes an existing VLAN from the Bridge, including automatically removing all interfaces from that VLAN before. The following error-messages are to be send, if the operation would fail: #[onf:VLAN cannot be deleted.]#, e.g. if the VLAN is required for some special service. #[onf:Referenced object is invalid.]#, if the referenced ForwardingConstruct does not belong to the VLAN layer.";
    input {
      leaf affected-vlan-fd {
        type leafref {
          path "/core-model:control-construct/core-model:forwarding-domain/core-model:uuid";
          require-instance false;
        }
        mandatory true;
        description
          "Reference of the VLAN Bridge, which holds the to be deleted VLAN.";
      }
      leaf obsolete-vlan-fc {
        type leafref {
          path "/core-model:control-construct/core-model:forwarding-domain/core-model:fc/core-model:uuid";
          require-instance false;
        }
        mandatory true;
        description
          "Reference of the to be deleted VLAN.";
      }
    }
  }

  augment "/core-model:control-construct/core-model:forwarding-domain" {
    when "derived-from-or-self(./core-model:layer-protocol-name, 'vlan-interface:LAYER_PROTOCOL_NAME_TYPE_VLAN_LAYER')";
    description
      "none";
    uses vlan-fd-spec;
  }
}
