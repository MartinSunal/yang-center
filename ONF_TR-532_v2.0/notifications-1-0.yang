module notifications-1-0 {
  yang-version 1.1;
  namespace "urn:onf:yang:notifications-1-0";
  prefix notifications;

  import ietf-yang-types {
    prefix yang;
  }

  organization
    "openBackhaul.com proposal to Open Networking Foundation (ONF)";
  contact
    "WG Web : https://github.com/openBackhaul/Overview
     WG List: Notifications@openBackhaul.com
     Editor : Thorsten Heinze
     Email  : Thorsten.Heinze@openBackhaul.com";
  description
    "Copyright 2023 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2023-09-20 {
    description
      "Model for the Transport SDN Introduction at Telefonica Germany.
       Please view https://github.com/openBackhaul/notifications/issues for changes.";
    reference
      "https://github.com/openBackhaul/notifications/tree/tsi: Model definition
       https://github.com/openBackhaul/onfCoreIm/tree/tsp: ONF TR-512 Core IM incl. Profile and enhanced Equipment definition";
  }

  /****************************************
   * package notifications
   **************************************/ 

  notification object-creation-notification {
    uses object-creation-notification;
    description
      "none";
  }

  grouping object-creation-notification {
    leaf counter {
      type int32;
      default "-1";
      config false;
      description
        "Counts object creation notifications.";
    }
    leaf timestamp {
      type yang:date-and-time;
      default "2010-11-20T14:00:00+01:00";
      config false;
      description
        "none";
    }
    leaf object-path {
      type instance-identifier;
      config false;
      mandatory true;
      description
        "Path from the top level element (e.g. ControlConstruct) to the object that got created. In YANG, it would be the container or list that got created.";
    }
    description
      "none";
  }

  notification object-deletion-notification {
    uses object-deletion-notification;
    description
      "none";
  }

  grouping object-deletion-notification {
    leaf counter {
      type int32;
      default "-1";
      config false;
      description
        "Counts object deletion notifications.";
    }
    leaf timestamp {
      type yang:date-and-time;
      default "2010-11-20T14:00:00+01:00";
      config false;
      description
        "none";
    }
    leaf object-path {
      type instance-identifier;
      config false;
      mandatory true;
      description
        "Path from the top level element (e.g. ControlConstruct) to the object that got deleted. In YANG, it would be the container or list that that got deleted.";
    }
    description
      "none";
  }

  notification attribute-value-changed-notification {
    uses attribute-value-changed-notification;
    description
      "none";
  }

  grouping attribute-value-changed-notification {
    leaf counter {
      type int32;
      default "-1";
      config false;
      description
        "Counts attribute value changed notifications.";
    }
    leaf timestamp {
      type yang:date-and-time;
      default "2010-11-20T14:00:00+01:00";
      config false;
      description
        "none";
    }
    leaf object-path {
      type instance-identifier;
      config false;
      mandatory true;
      description
        "Path from the top level element (e.g ControlConstruct) to the object that holds the attribute that changed its value. In YANG, it would be the parent data node e.g. container or list that contains the leaf.";
    }
    leaf attribute-name {
      type string;
      default "attribute-name-not-yet-defined";
      config false;
      description
        "Name of the attribute that has changed its value. In YANG, it would be the name of the leaf or leaflist that changed its value.";
    }
    leaf new-value {
      type string;
      default "New value not yet defined.";
      config false;
      description
        "Attribute value converted to a string (xml, json, ...)";
    }
    description
      "none";
  }

  /****************************************
   * grouping statements for object classes
   **************************************/ 
  /****************************************
   * typedef statements
   **************************************/ 
  /*********************************************
   * grouping statements for complex data types
   *******************************************/ 
}
