module mac-interface-1-0 {
  yang-version 1.1;
  namespace "urn:onf:yang:mac-interface-1-0";
  prefix mac-interface;

  import ietf-yang-types {
    prefix yang;
  }
  import core-model-1-4 {
    prefix core-model;
  }

  organization
    "openBackhaul.com proposal to Open Networking Foundation (ONF)";
  contact
    "WG Web : https://github.com/openBackhaul/Overview
     WG List: MacInterface@openBackhaul.com
     Editor : Thorsten Heinze
     Email  : Thorsten.Heinze@openBackhaul.com";
  description
    "Technology specific interface definition for Ethernet MAC interfaces according to IEEE 802.1

     Copyright 2024 openBackhaul.com

     Licensed under the Apache License, Version 2.0 (the 'License');
     you may not use this file except in compliance with the License.
     You may obtain a copy of the License at
     http://www.apache.org/licenses/LICENSE-2.0
     Unless required by applicable law or agreed to in writing, software
     distributed under the License is distributed on an 'AS IS' BASIS,
     WITHOUT WARRANTIES OR CONDITIONS OF ANY KIND, either express or implied.
     See the License for the specific language governing permissions and
     limitations under the License.";

  revision 2024-01-05 {
    description
      "Model for the Transport SDN Introduction at Telefonica Germany.
       Please view https://github.com/openBackhaul/macInterface/issues for changes.";
    reference
      "https://github.com/openBackhaul/macInterface/tree/tsi: Model definition
       https://github.com/openBackhaul/onfCoreIm/tree/tsi: ONF TR-512 Core IM incl. Profile and enhanced Equipment definition";
  }
  revision 2022-03-25 {
    description
      "Model for the Transport SDN Pilot at Telefonica Germany.
       Please view https://github.com/openBackhaul/macInterface/issues for changes.";
    reference
      "https://github.com/openBackhaul/macInterface/tree/tsi: Model definition
       https://github.com/openBackhaul/onfCoreIm/tree/tsi: ONF TR-512 Core IM incl. Profile and enhanced Equipment definition";
  }
  revision 2020-09-03 {
    description
      "Model for the Transport SDN Pilot at Telefonica Germany.
       Please view https://github.com/openBackhaul/macInterface/issues for changes.";
    reference
      "https://github.com/openBackhaul/macInterface/tree/tsi: Model definition
       https://github.com/openBackhaul/onfCoreIm/tree/tsi: ONF TR-512 Core IM incl. Profile and enhanced Equipment definition";
  }
  revision 2020-01-23 {
    description
      "Model for the Transport SDN Pilot at Telefonica Germany.
       Please view https://github.com/openBackhaul/macInterface/issues for changes.";
    reference
      "https://github.com/openBackhaul/macInterface/tree/tsi: Model definition
       https://github.com/openBackhaul/onfCoreIm/tree/tsi: ONF TR-512 Core IM incl. Profile and enhanced Equipment definition";
  }
  revision 2019-07-11 {
    description
      "Model for the Transport SDN Pilot at Telefonica Germany.
       Please view https://github.com/openBackhaul/macInterface/issues for changes.";
    reference
      "https://github.com/openBackhaul/macInterface/tree/tsi: Model definition
       https://github.com/openBackhaul/onfCoreIm/tree/tsi: ONF TR-512 Core IM incl. Profile and enhanced Equipment definition";
  }

  identity LAYER_PROTOCOL_NAME_TYPE_MAC_LAYER {
    base core-model:LAYER_PROTOCOL_NAME_TYPE;
    description
      "none";
  }

  /*********************************************
   * grouping statements for complex data types
   *******************************************/ 

  identity LOOP_BACK_TYPE {
    description
      "none";
  }

  identity LOOP_BACK_TYPE_NONE {
    base LOOP_BACK_TYPE;
    description
      "none";
  }

  identity LOOP_BACK_TYPE_BACK_TO_LOCAL {
    base LOOP_BACK_TYPE;
    description
      "Returning Ethernet frames of the local site on the Ethernet MAC interface back to the local site.";
  }

  identity LOOP_BACK_TYPE_BACK_TO_REMOTE {
    base LOOP_BACK_TYPE;
    description
      "Returning Ethernet frames of the remote site on the Ethernet MAC interface back to the remote site.";
  }

  identity LOOP_BACK_TYPE_NOT_YET_DEFINED {
    base LOOP_BACK_TYPE;
    description
      "none";
  }

  identity FRAGMENTATION_TYPE {
    description
      "none";
  }

  identity FRAGMENTATION_TYPE_DISABLE {
    base FRAGMENTATION_TYPE;
    description
      "none";
  }

  identity FRAGMENTATION_TYPE_ENABLE_256_BYTE {
    base FRAGMENTATION_TYPE;
    description
      "none";
  }

  identity FRAGMENTATION_TYPE_ENABLE_512_BYTE {
    base FRAGMENTATION_TYPE;
    description
      "none";
  }

  identity FRAGMENTATION_TYPE_NOT_YET_DEFINED {
    base FRAGMENTATION_TYPE;
    description
      "none";
  }

  identity FRAME_FORMAT_TYPE {
    description
      "none";
  }

  identity FRAME_FORMAT_TYPE_ETHERNET_2 {
    base FRAME_FORMAT_TYPE;
    description
      "none";
  }

  identity FRAME_FORMAT_TYPE_802.2_SNAP {
    base FRAME_FORMAT_TYPE;
    description
      "none";
  }

  identity FRAME_FORMAT_TYPE_802.2_LLC {
    base FRAME_FORMAT_TYPE;
    description
      "none";
  }

  identity FRAME_FORMAT_TYPE_802.3 {
    base FRAME_FORMAT_TYPE;
    description
      "none";
  }

  identity FRAME_FORMAT_TYPE_NOT_YET_DEFINED {
    base FRAME_FORMAT_TYPE;
    description
      "none";
  }

  identity FLOW_CONTROL_MODE_TYPE {
    description
      "none";
  }

  identity FLOW_CONTROL_MODE_TYPE_NONE {
    base FLOW_CONTROL_MODE_TYPE;
    description
      "Flow Control is switched off.";
  }

  identity FLOW_CONTROL_MODE_TYPE_SEND_ONLY {
    base FLOW_CONTROL_MODE_TYPE;
    description
      "Only sending of pause frames according to IEEE 802.3x (Ethernet Flow Control).";
  }

  identity FLOW_CONTROL_MODE_TYPE_RECEIVE_ONLY {
    base FLOW_CONTROL_MODE_TYPE;
    description
      "Only listening for incoming pause frames according to IEEE 802.3x (Ethernet Flow Control).";
  }

  identity FLOW_CONTROL_MODE_TYPE_SEND_AND_RECEIVE {
    base FLOW_CONTROL_MODE_TYPE;
    description
      "Sending and listening for pause frames according to IEEE 802.3x (Ethernet Flow Control).";
  }

  identity FLOW_CONTROL_MODE_TYPE_AUTO_NEGOTIATION {
    base FLOW_CONTROL_MODE_TYPE;
    description
      "none";
  }

  identity FLOW_CONTROL_MODE_TYPE_NOT_YET_DEFINED {
    base FLOW_CONTROL_MODE_TYPE;
    description
      "none";
  }

  identity LOOP_DETECTION_RESULT_TYPE {
    description
      "none";
  }

  identity LOOP_DETECTION_RESULT_TYPE_LOOP_DETECTED {
    base LOOP_DETECTION_RESULT_TYPE;
    description
      "none";
  }

  identity LOOP_DETECTION_RESULT_TYPE_NO_LOOP_DETECTED {
    base LOOP_DETECTION_RESULT_TYPE;
    description
      "none";
  }

  identity LOOP_DETECTION_RESULT_TYPE_DETECTION_SWITCHED_OFF {
    base LOOP_DETECTION_RESULT_TYPE;
    description
      "none";
  }

  identity LOOP_DETECTION_RESULT_TYPE_NOT_YET_DEFINED {
    base LOOP_DETECTION_RESULT_TYPE;
    description
      "none";
  }

  identity INTERFACE_STATUS_TYPE {
    description
      "none";
  }

  identity INTERFACE_STATUS_TYPE_UP {
    base INTERFACE_STATUS_TYPE;
    description
      "Ready to pass packets. It is expected that the LogicalTerminationPoint::operationalState attribute is expressing this logical layer being available for use (means: ENABLED), while this value occurs.";
  }

  identity INTERFACE_STATUS_TYPE_DOWN {
    base INTERFACE_STATUS_TYPE;
    description
      "The interface does not pass any packets. It is expected that the LogicalTerminationPoint::operationalState attribute is expressing this logical layer being NOT available for use (means: DISABLED), while this value occurs.";
  }

  identity INTERFACE_STATUS_TYPE_SHUT_DUE_LOOP {
    base INTERFACE_STATUS_TYPE;
    description
      "Only relevant if (loopPortShutDownIsAvail==1) AND (loopPortShutDownIsOn==1). 1 = port has been automatically shut down, because an Ethernet loop has been detected on this interface.";
  }

  identity INTERFACE_STATUS_TYPE_TESTING {
    base INTERFACE_STATUS_TYPE;
    description
      "In some test mode.  No operational packets can be passed. It is expected that the LogicalTerminationPoint::operationalState attribute is expressing this logical layer being NOT available for use (means: DISABLED), while this value occurs.";
  }

  identity INTERFACE_STATUS_TYPE_UNKNOWN {
    base INTERFACE_STATUS_TYPE;
    description
      "Status cannot be determined for some reason. While this value occurs, the LogicalTerminationPoint::operationalState attribute, which is expressing the availability of the logical layer for being used, might have either ENABLED or DISABLED as value.";
  }

  identity INTERFACE_STATUS_TYPE_DORMANT {
    base INTERFACE_STATUS_TYPE;
    description
      "Waiting for some external event. It is expected that the LogicalTerminationPoint::operationalState attribute is expressing this logical layer being available for use (means: ENABLED), while this value occurs.";
  }

  identity INTERFACE_STATUS_TYPE_NOT_PRESENT {
    base INTERFACE_STATUS_TYPE;
    description
      "Some component (typically hardware) is missing. It is expected that the LogicalTerminationPoint::operationalState attribute is expressing this logical layer being NOT available for use (means: DISABLED), while this value occurs.";
  }

  identity INTERFACE_STATUS_TYPE_NOT_YET_DEFINED {
    base INTERFACE_STATUS_TYPE;
    description
      "While this value occurs, the LogicalTerminationPoint::operationalState attribute, which is expressing the availability of the logical layer for being used, might have either ENABLED or DISABLED as value.";
  }

  /****************************************
   * typedef statements
   **************************************/ 

  typedef loop-back-type {
    type identityref {
      base LOOP_BACK_TYPE;
    }
    description
      "none";
  }

  typedef fragmentation-type {
    type identityref {
      base FRAGMENTATION_TYPE;
    }
    description
      "none";
  }

  typedef frame-format-type {
    type identityref {
      base FRAME_FORMAT_TYPE;
    }
    description
      "none";
  }

  typedef flow-control-mode-type {
    type identityref {
      base FLOW_CONTROL_MODE_TYPE;
    }
    description
      "none";
  }

  typedef loop-detection-result-type {
    type identityref {
      base LOOP_DETECTION_RESULT_TYPE;
    }
    description
      "none";
  }

  /****************************************
   * package super-types
   **************************************/ 

  typedef interface-status-type {
    type identityref {
      base INTERFACE_STATUS_TYPE;
    }
    description
      "Current Interface Status";
  }

  /****************************************
   * grouping statements for object classes
   **************************************/ 

  grouping mac-interface-lp-spec {
    description
      "none";
    container mac-interface-pac {
      description
        "none";
      uses mac-interface-pac;
    }
  }

  grouping mac-interface-pac {
    description
      "none";
    container mac-interface-capability {
      config false;
      description
        "none";
      uses mac-interface-capability;
    }
    container mac-interface-configuration {
      description
        "none";
      uses mac-interface-configuration;
    }
    container mac-interface-status {
      config false;
      description
        "none";
      uses mac-interface-status;
    }
  }

  grouping mac-interface-capability {
    description
      "none";
    leaf hardware-mac-address {
      type string;
      default "00:00:00:00:00:00";
      config false;
      description
        "Hardware MAC address of the interface.";
    }
    leaf mac-address-configuration-is-avail {
      type boolean;
      default "false";
      config false;
      description
        "1 = Device supports overwriting the hardware MAC address.";
    }
    leaf-list supported-maximum-frame-size-list {
      type int16;
      units "Byte";
      default "-1";
      config false;
      description
        "Must exclusively contain values, which are actually configurable at the hardware (except the default value -1, which has to be represented if maximum frame size cannot be configured at all). Might be all or just a subset of values actually configurable at the hardware.";
    }
    leaf-list supported-frame-format-list {
      type frame-format-type;
      config false;
      min-elements 1;
      description
        "List of supported Ethernet frame formats";
    }
    leaf-list supported-flow-control-mode-list {
      type flow-control-mode-type;
      config false;
      min-elements 1;
      max-elements 5;
      description
        "List of potential configurations of the Flow Control.";
    }
    leaf link-loss-forwarding-is-avail {
      type boolean;
      default "false";
      config false;
      description
        "1 = Sending a Link Loss message in case of link failure is supported by the device.";
    }
    leaf-list supported-link-loss-forwarding-delay-list {
      type int8;
      units "100ms";
      default "-1";
      config false;
      description
        "Must exclusively contain values, which are actually configurable at the hardware (except the default value -1, which has to be represented if link loss forwarding delay cannot be configured at all). Might be all or just a subset of values actually configurable at the hardware.";
    }
    leaf broadcast-frame-suppression-is-avail {
      type boolean;
      default "false";
      config false;
      description
        "1 = Interface is supporting limiting the maximum share of broadcast frames.";
    }
    leaf loop-port-shut-down-is-avail {
      type boolean;
      default "false";
      config false;
      description
        "1 = Device is supporting automated shut down of ports, which are affected by an Ethernet loop.";
    }
    leaf loop-detection-is-avail {
      type boolean;
      default "false";
      config false;
      description
        "1 = Device is supporting a feature for detecting Ethernet loops on this interface.";
    }
    leaf admin-shut-down-is-avail {
      type boolean;
      default "false";
      config false;
      description
        "1 = Manual switching on and off of the interface without deleting it (underlying OSI network layers are also not affected) is available.";
    }
    leaf-list supported-loop-back-kind-list {
      type loop-back-type;
      config false;
      min-elements 1;
      max-elements 3;
      description
        "List of supported kinds of looping back.";
    }
    leaf maintenance-timer-range {
      type string;
      units "s";
      default "Range of the maintenance timer not yet defined.";
      config false;
      description
        "Available time periods for maintenance configurations to be described. Concrete values shall be separated by commas (e.g. '10, 60, 360'). Ranges shall be expressed as two values separated by a minus (e.g. '10-360').";
    }
    leaf statistics-is-avail {
      type boolean;
      default "false";
      config false;
      description
        "1 = Continuous statistics counters are available.";
    }
  }

  grouping mac-interface-configuration {
    description
      "none";
    leaf interface-name {
      type string;
      default "Interface name not yet defined.";
      description
        "Description of the interface, could be a name, could be a number. Free text field to be filled by the operator.";
    }
    leaf mac-address-configuration-is-on {
      type boolean;
      default "false";
      description
        "Only relevant if (macAddressConfigurationIsAvail==1). 1 = Activates overwriting the hardware MAC address by MacInterfaceConfiguration::configuredMacAddress.";
    }
    leaf configured-mac-address {
      type string;
      default "00:00:00:00:00:00";
      description
        "Only relevant if (macAddressConfigurationIsAvail==1 AND macAddressConfigurationIsOn==1). Overwriting the hardware MAC address with the configured value.";
    }
    leaf maximum-frame-size {
      type int16;
      units "Byte";
      default "-1";
      description
        "This value describes the maximum size of the Ethernet frame (in Byte) before sending. Validation result shall reflect hardware characteristics, even if these are exceeding the values stated in MacInterfaceCapability::supportedMaximumFrameSizeList. If a value, which is not supported by the hardware, would be tried to be configured, the device-software or mediator-software might either respond with operation-failed tag and error message '...Configuration value out of range of hardware capabilities...' or it could map the sent configuration value on the closest value, which is actually supported by the hardware. Configuration attempts with values lower than the minimum value or higher than the maximum value of the 'supportedMaximumFrameSizeList' must be answered with operation-failed tag and the error message '...Configuration value out of range of hardware capabilities...'.";
    }
    leaf fragmentation-allowed {
      type fragmentation-type;
      default "FRAGMENTATION_TYPE_NOT_YET_DEFINED";
      description
        "none";
    }
    leaf transmitted-frame-format {
      type frame-format-type;
      default "FRAME_FORMAT_TYPE_NOT_YET_DEFINED";
      description
        "Configuration of the format of the transmitted Ethernet frames.";
    }
    leaf flow-control-mode {
      type flow-control-mode-type;
      default "FLOW_CONTROL_MODE_TYPE_NOT_YET_DEFINED";
      description
        "Configures the mode of operation of Flow Control according to IEEE 802.3x on this interface.";
    }
    leaf link-loss-forwarding-is-on {
      type boolean;
      default "false";
      description
        "1 = Sending a Link Loss message in case of link failure is activated.";
    }
    leaf link-loss-forwarding-delay {
      type int8;
      units "100ms";
      default "-1";
      description
        "Delay (in 100ms steps) between a detected link failure and sending of a Link Loss message. In case of 1+1 hot stand by protection of a microwave, make sure configured value is higher than 5 (500ms). Validation result shall reflect hardware characteristics, even if these are exceeding the values stated in MacInterfaceCapability::supportedLinkLossForwardingDelayList. If a value, which is not supported by the hardware, would be tried to be configured, the device-software or mediator-software might either respond with operation-failed tag and error message '...Configuration value out of range of hardware capabilities...' or it could map the sent configuration value on the closest value, which is actually supported by the hardware. Configuration attempts with values lower than the minimum value or higher than the maximum value of the 'supportedLinkLossForwardingDelayList' must be answered with operation-failed tag and the error message '...Configuration value out of range of hardware capabilities...'.";
    }
    leaf broadcast-frame-suppression-is-on {
      type boolean;
      default "false";
      description
        "1 = Limiting the share of broadcast frames is activated.";
    }
    leaf maximum-share-of-broadcast-frames {
      type int8;
      units "%";
      default "-1";
      description
        "Threshold for Broadcast frames becoming discarded in %. Value range from 0 to 100.";
    }
    leaf loop-port-shut-down-is-on {
      type boolean;
      default "false";
      description
        "1 = Feature for automated shut down in case of an Ethernet loop is activated on this interface.";
    }
    leaf loop-detection-is-on {
      type boolean;
      default "false";
      description
        "Maintenance Feature. 1 = Checking for Ethernet loops on this interface is currently switched on.";
    }
    leaf loop-back-kind-on {
      type loop-back-type;
      default "LOOP_BACK_TYPE_NOT_YET_DEFINED";
      description
        "Maintenance Feature. Configuration of a loop back of Ethernet frames on this interface.";
    }
    leaf maintenance-timer {
      type int32;
      units "s";
      default "-1";
      description
        "Time of existence of any maintenance configuration. 0 = maintenance timer is switched off. Valid values are defined in *Capability::maintenanceTimerRange.";
    }
    leaf statistics-is-on {
      type boolean;
      default "false";
      description
        "Only relevant if (statisticsIsAvail==1). 1 = Continuous statistics counters are switched on.";
    }
  }

  grouping mac-interface-status {
    description
      "none";
    leaf interface-status {
      type interface-status-type;
      default "INTERFACE_STATUS_TYPE_NOT_YET_DEFINED";
      config false;
      description
        "Operational status of the interface.";
    }
    leaf mac-address-cur {
      type string;
      default "00:00:00:00:00:00";
      config false;
      description
        "If (macAddressConfigurationIsAvail==0), maxAddressCur = MacInterfaceCapability::hardwareMacAddress. If (macAddressConfigurationIsAvail==1 AND macAddressConfigurationIsOn==1), maxAddressCur = MacInterfaceConfiguration::configuredMacAddress.";
    }
    leaf received-ethernet-frame-format-cur {
      type frame-format-type;
      default "FRAME_FORMAT_TYPE_NOT_YET_DEFINED";
      config false;
      description
        "Ethernet frame format of the currently received frames.";
    }
    leaf flow-control-mode-cur {
      type flow-control-mode-type;
      default "FLOW_CONTROL_MODE_TYPE_NOT_YET_DEFINED";
      config false;
      description
        "Currently operative mode (none, send, receive, both) of operation of the Flow Control according to IEEE 802.3x on this interface.";
    }
    leaf loop-detection-result {
      type loop-detection-result-type;
      default "LOOP_DETECTION_RESULT_TYPE_NOT_YET_DEFINED";
      config false;
      description
        "Result of the Ethernet loop detection feature.";
    }
    leaf loop-back-kind-up {
      type loop-back-type;
      default "LOOP_BACK_TYPE_NOT_YET_DEFINED";
      config false;
      description
        "The currently active (not just configured) type of loop back.";
    }
    leaf statistics-is-up {
      type boolean;
      default "false";
      config false;
      description
        "1 = Statistics are currently collected and aggregated.";
    }
    leaf timestamp {
      type yang:date-and-time;
      default "2010-11-20T14:00:00+01:00";
      config false;
      description
        "The timestamp associated with when the statistic values were read/retrieved.";
    }
    leaf last-10-sec-frame-input-rate {
      type int32;
      units "frame/s";
      default "-1";
      config false;
      description
        "Frame receive rate at this MAC interface over the last 10 second interval.";
    }
    leaf last-10-sec-frame-output-rate {
      type int32;
      units "frame/s";
      default "-1";
      config false;
      description
        "Frame transmit rate at this MAC interface over the last 10 second interval.";
    }
    leaf oversized-frames-ingress {
      type int64;
      units "frame";
      default "-1";
      config false;
      description
        "The total number of frames received that were longer than 1518 octets (excluding framing bits, but including FCS octets) and were otherwise well formed.";
    }
    leaf undersized-frames-ingress {
      type int64;
      units "frame";
      default "-1";
      config false;
      description
        "The total number of frames received that were less than 64 octets long (excluding framing bits, but including FCS octets) and were otherwise well formed.";
    }
    leaf jabber-frames-ingress {
      type int64;
      units "frame";
      default "-1";
      config false;
      description
        "Number of jabber frames received on the interface. Jabber frames are typically defined as oversize frames which also have a bad CRC. Implementations may use slightly different definitions of what constitutes a jabber frame. Often indicative of a NIC hardware problem.";
    }
    leaf fragmented-frames-ingress {
      type int64;
      units "frame";
      default "-1";
      config false;
      description
        "The total number of frames received that were less than 64 octets in length (excluding framing bits but including FCS octets) and had either a bad Frame Check Sequence (FCS) with an integral number of octets (FCS Error) or a bad FCS with a non-integral number of octets (Alignment Error).";
    }
    leaf unknown-protocol-frames-input {
      type int64;
      units "frame";
      default "-1";
      config false;
      description
        "Total number of received frames that were transporting an unknown protocol.";
    }
  }

  augment "/core-model:control-construct/core-model:logical-termination-point/core-model:layer-protocol" {
    when "derived-from-or-self(./core-model:layer-protocol-name, 'mac-interface:LAYER_PROTOCOL_NAME_TYPE_MAC_LAYER')";
    description
      "none";
    uses mac-interface-lp-spec;
  }
}
